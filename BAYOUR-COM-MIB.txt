BAYOUR-COM-MIB DEFINITIONS ::= BEGIN
-- $Id: BAYOUR-COM-MIB.txt,v 1.3 2005-04-01 12:42:27 turbo Exp $

IMPORTS
    MODULE-IDENTITY, OBJECT-TYPE,
    NOTIFICATION-TYPE, Gauge32, enterprises FROM SNMPv2-SMI;

bayourcom MODULE-IDENTITY
    LAST-UPDATED "200504010000Z"  -- April 1, 2005
    ORGANIZATION "Bayour.COM"
    CONTACT-INFO
      "Postal:   Turbo Fredriksson
                 Naverlursgatan 8
                 421 44 Vastra Frolunda
                 Sweden
       Tel:      +46 704-697645
       E-Mail:   turbo@bayour.com"
    DESCRIPTION  "The MIB module defines the Bayour.COM Bind9 statistics"

    REVISION     "200504011437Z" -- April 1, 2005 - 14:37
    DESCRIPTION  "Changed recursive to recursion;
                  Changed failed to failure;
                  This according to original Bind9 definitions."
    ::= { enterprises 8767 }

snmp            OBJECT IDENTIFIER ::= { bayourcom 2 }
bind9stats	OBJECT IDENTIFIER ::= { snmp 1 }
  success       OBJECT IDENTIFIER ::= { bind9stats 1 }
   total   OBJECT-TYPE
     SYNTAX      Gauge32
     MAX-ACCESS  read-only
     STATUS      current
     DESCRIPTION "Total number of requests"
     ::= { success 1 }
   forward OBJECT-TYPE
     SYNTAX      Gauge32
     MAX-ACCESS  read-only
     STATUS      current
     DESCRIPTION "Forwarded number of requests"
     ::= { success 2 }
   reverse OBJECT-TYPE
     SYNTAX      Gauge32
     MAX-ACCESS  read-only
     STATUS      current
     DESCRIPTION "Reversed number of requests"
     ::= { success 3 }

  referral      OBJECT IDENTIFIER ::= { bind9stats 2 }
   total   OBJECT-TYPE
     SYNTAX      Gauge32
     MAX-ACCESS  read-only
     STATUS      current
     DESCRIPTION "Total number of requests"
     ::= { referral 1 }
   forward OBJECT-TYPE
     SYNTAX      Gauge32
     MAX-ACCESS  read-only
     STATUS      current
     DESCRIPTION "Forwarded number of requests"
     ::= { referral 2 }
   reverse OBJECT-TYPE
     SYNTAX      Gauge32
     MAX-ACCESS  read-only
     STATUS      current
     DESCRIPTION "Reversed number of requests"
     ::= { referral 3 }

  nxrrset       OBJECT IDENTIFIER ::= { bind9stats 3 }
   total   OBJECT-TYPE
     SYNTAX      Gauge32
     MAX-ACCESS  read-only
     STATUS      current
     DESCRIPTION "Total number of requests"
     ::= { nxrrset 1 }
   forward OBJECT-TYPE
     SYNTAX      Gauge32
     MAX-ACCESS  read-only
     STATUS      current
     DESCRIPTION "Forwarded number of requests"
     ::= { nxrrset 2 }
   reverse OBJECT-TYPE
     SYNTAX      Gauge32
     MAX-ACCESS  read-only
     STATUS      current
     DESCRIPTION "Reversed number of requests"
     ::= { nxrrset 3 }

  nxdomain      OBJECT IDENTIFIER ::= { bind9stats 4 }
   total   OBJECT-TYPE
     SYNTAX      Gauge32
     MAX-ACCESS  read-only
     STATUS      current
     DESCRIPTION "Total number of requests"
     ::= { nxdomain 1 }
   forward OBJECT-TYPE
     SYNTAX      Gauge32
     MAX-ACCESS  read-only
     STATUS      current
     DESCRIPTION "Forwarded number of requests"
     ::= { nxdomain 2 }
   reverse OBJECT-TYPE
     SYNTAX      Gauge32
     MAX-ACCESS  read-only
     STATUS      current
     DESCRIPTION "Reversed number of requests"
     ::= { nxdomain 3 }

  recursion     OBJECT IDENTIFIER ::= { bind9stats 5 }
   total   OBJECT-TYPE
     SYNTAX      Gauge32
     MAX-ACCESS  read-only
     STATUS      current
     DESCRIPTION "Total number of requests"
     ::= { recursion 1 }
   forward OBJECT-TYPE
     SYNTAX      Gauge32
     MAX-ACCESS  read-only
     STATUS      current
     DESCRIPTION "Forwarded number of requests"
     ::= { recursion 2 }
   reverse OBJECT-TYPE
     SYNTAX      Gauge32
     MAX-ACCESS  read-only
     STATUS      current
     DESCRIPTION "Reversed number of requests"
     ::= { recursion 3 }

  failure        OBJECT IDENTIFIER ::= { bind9stats 6 }
   total   OBJECT-TYPE
     SYNTAX      Gauge32
     MAX-ACCESS  read-only
     STATUS      current
     DESCRIPTION "Total number of requests"
     ::= { failure 1 }
   forward OBJECT-TYPE
     SYNTAX      Gauge32
     MAX-ACCESS  read-only
     STATUS      current
     DESCRIPTION "Forwarded number of requests"
     ::= { failure 2 }
    reverse OBJECT-TYPE
      SYNTAX      Gauge32
      MAX-ACCESS  read-only
      STATUS      current
      DESCRIPTION "Reversed number of requests"
      ::= { failure 3 }
END
